// Generated by SpecAlive from the IR (specalive/generate/sysml.py). Regenerate, do not edit.
package two_tank_sequence {
    doc /* model: two_tank_sequence
     * description: Two-tank fill/transfer/drain demonstrator: TK-101 is filled through XV-101, transferred to TK-102 through XV-102 and drained through XV-103, sequenced by PLC-101 from LT-101/LT-102 levels and START/STOP/SHUT pushbuttons. Hand-written golden IR from the L1 bundle with the CR-004 effective parameter set.
     * generated from the IR by SpecAlive (generate/sysml.py); regenerate, do not edit
     */
    private import ISQ::*;
    private import SI::*;
    private import ScalarValues::*;

    calc def timer_expired {
        doc /* IR expression language: true once the timer's state has been active for its duration */
        in timer : TimeValue;
        return : Boolean;
    }

    action def start_timer {
        doc /* IR action: start the timer from its full duration */
        in timer : TimeValue;
    }

    action def save_history {
        doc /* IR action: remember the active state and the remaining time of its timers */
    }

    action def clear_history {
        doc /* IR action: forget the remembered state */
    }

    port def BoolSignal {
        doc /* domain: signal_bool */
        out attribute value : Boolean;
    }

    port def FluidPort {
        doc /* domain: fluid */
        out attribute volume_flow : VolumeFlowRateValue;
    }

    port def RealSignal {
        doc /* domain: signal_real */
        out attribute value : Real;
    }

    part def CommandButton {
        doc /* kind: command_button
         * catalogue: Momentary operator pushbutton; true for a short pulse at each press time.
         */
        port cmd_out : BoolSignal;
    }

    part def FluidSink {
        doc /* kind: fluid_sink
         * catalogue: Ideal drain boundary; accepts whatever flow arrives.
         */
        port inlet : ~FluidPort;
    }

    part def FluidSource {
        doc /* kind: fluid_source
         * catalogue: Ideal supply boundary; delivers whatever flow downstream draws.
         */
        port outlet : FluidPort;
    }

    part def LevelSensor {
        doc /* kind: level_sensor
         * catalogue: Level transmitter passing the measured level to the controller unchanged.
         */
        port level_in : ~RealSignal;
        port level_out : RealSignal;
    }

    part def OnOffValve {
        doc /* kind: on_off_valve
         * catalogue: Two-position isolation valve treated as an ideal Boolean flow switch passing its nominal flow when commanded open.
         */
        attribute nominal_flow : VolumeFlowRateValue;
        attribute open_stroke_time : TimeValue;
        port cmd_in : ~BoolSignal;
        port inlet : ~FluidPort;
        port outlet : FluidPort;
    }

    part def SequenceController {
        doc /* kind: sequence_controller
         * catalogue: Discrete sequence controller generated from the IR state machine it owns.
         * ports come from each IR part and are declared on its usage
         */
        attribute scan_time : TimeValue;
        attribute wait_after_drain : TimeValue;
        attribute wait_after_fill : TimeValue;
        attribute wait_after_transfer : TimeValue;
    }

    part def Tank {
        doc /* kind: tank
         * catalogue: Open vertical tank; level is the stored volume over a constant cross-section.
         */
        attribute area : AreaValue;
        attribute height : LengthValue;
        attribute high_level : LengthValue;
        attribute initial_level : LengthValue;
        attribute low_level : LengthValue;
        attribute max_working_level : LengthValue;
        port inlet : ~FluidPort;
        port level_out : RealSignal;
        port outlet : FluidPort;
    }

    attribute def shut_cmd {
        doc /* ir: shut_cmd
         * event of plc_101_sequence: rising edge of port plc_101_shut
         */
    }

    attribute def start_cmd {
        doc /* ir: start_cmd
         * event of plc_101_sequence: rising edge of port plc_101_start
         */
    }

    attribute def stop_cmd {
        doc /* ir: stop_cmd
         * event of plc_101_sequence: rising edge of port plc_101_stop
         */
    }

    state def plc_101_sequence {
        doc /* ir: plc_101_sequence
         * owner: plc_101
         * source: cds_02 @ §2 State Definitions, FILL_T1 (+11 more)
         * ASSUMPTION as_event_driven_controller: The controller reacts to events and thresholds immediately rather than on its 100 ms scan; the scan time is recorded but not simulated.
         */
        in attribute plc_101_level1 : Real;
        in attribute plc_101_level2 : Real;
        in attribute tk_101_high_level : LengthValue;
        in attribute tk_101_low_level : LengthValue;
        in attribute tk_102_low_level : LengthValue;
        out attribute plc_101_valve1 : Boolean;
        out attribute plc_101_valve2 : Boolean;
        out attribute plc_101_valve3 : Boolean;
        attribute wait_after_fill_timer : TimeValue {
            doc /* ir: wait_after_fill_timer
             * duration: parameter plc_101_wait_after_fill; counts only while its state is active
             */
        }
        attribute wait_after_transfer_timer : TimeValue {
            doc /* ir: wait_after_transfer_timer
             * duration: parameter plc_101_wait_after_transfer; counts only while its state is active
             */
        }
        attribute wait_after_drain_timer : TimeValue {
            doc /* ir: wait_after_drain_timer
             * duration: parameter plc_101_wait_after_drain; counts only while its state is active
             */
        }
        entry; then idle;
        state idle {
            doc /* ir: idle
             * name: IDLE
             */
            entry action {
                assign plc_101_valve1 := false;
                assign plc_101_valve2 := false;
                assign plc_101_valve3 := false;
            }
        }
        state fill_t1 {
            doc /* ir: fill_t1
             * name: FILL_T1
             * tags: FILL
             */
            entry action {
                assign plc_101_valve1 := true;
                assign plc_101_valve2 := false;
                assign plc_101_valve3 := false;
            }
        }
        state wait_after_fill {
            doc /* ir: wait_after_fill
             * name: WAIT_AFTER_FILL
             * tags: HOLD1
             */
            entry action {
                assign plc_101_valve1 := false;
                assign plc_101_valve2 := false;
                assign plc_101_valve3 := false;
            }
        }
        state transfer_t1_t2 {
            doc /* ir: transfer_t1_t2
             * name: TRANSFER_T1_T2
             * tags: TRANSFER
             */
            entry action {
                assign plc_101_valve1 := false;
                assign plc_101_valve2 := true;
                assign plc_101_valve3 := false;
            }
        }
        state wait_after_transfer {
            doc /* ir: wait_after_transfer
             * name: WAIT_AFTER_TRANSFER
             * tags: HOLD2
             */
            entry action {
                assign plc_101_valve1 := false;
                assign plc_101_valve2 := false;
                assign plc_101_valve3 := false;
            }
        }
        state drain_t2 {
            doc /* ir: drain_t2
             * name: DRAIN_T2
             * tags: DRAIN
             */
            entry action {
                assign plc_101_valve1 := false;
                assign plc_101_valve2 := false;
                assign plc_101_valve3 := true;
            }
        }
        state wait_after_drain {
            doc /* ir: wait_after_drain
             * name: WAIT_AFTER_DRAIN
             * tags: HOLD3
             */
            entry action {
                assign plc_101_valve1 := false;
                assign plc_101_valve2 := false;
                assign plc_101_valve3 := false;
            }
        }
        state paused {
            doc /* ir: paused
             * name: PAUSED
             */
            entry action {
                assign plc_101_valve1 := false;
                assign plc_101_valve2 := false;
                assign plc_101_valve3 := false;
            }
        }
        state shutdown {
            doc /* ir: shutdown
             * name: SHUTDOWN
             */
            entry action {
                assign plc_101_valve1 := false;
                assign plc_101_valve2 := true;
                assign plc_101_valve3 := true;
            }
        }
        state history {
            doc /* resume target: the state saved by the last save_history (UML shallow history); SysML v2 has no history pseudostate, so the IR's reserved target is a state here */
        }
        transition tr_idle_shut first idle accept shut_cmd do action : clear_history then shutdown {
            doc /* ir: tr_idle_shut
             * priority: 1
             */
        }
        transition tr_idle_start first idle accept start_cmd then fill_t1 {
            doc /* ir: tr_idle_start
             * priority: 3
             */
        }
        transition tr_fill_t1_shut first fill_t1 accept shut_cmd do action : clear_history then shutdown {
            doc /* ir: tr_fill_t1_shut
             * priority: 1
             */
        }
        transition tr_fill_t1_stop first fill_t1 accept stop_cmd do action : save_history then paused {
            doc /* ir: tr_fill_t1_stop
             * priority: 2
             */
        }
        transition tr_fill_t1_high first fill_t1 if plc_101_level1 >= tk_101_high_level do action : start_timer { in timer = wait_after_fill_timer; } then wait_after_fill {
            doc /* ir: tr_fill_t1_high
             * priority: 4
             */
        }
        transition tr_wait_after_fill_shut first wait_after_fill accept shut_cmd do action : clear_history then shutdown {
            doc /* ir: tr_wait_after_fill_shut
             * priority: 1
             */
        }
        transition tr_wait_after_fill_stop first wait_after_fill accept stop_cmd do action : save_history then paused {
            doc /* ir: tr_wait_after_fill_stop
             * priority: 2
             */
        }
        transition tr_wait_after_fill_done first wait_after_fill if timer_expired(wait_after_fill_timer) then transfer_t1_t2 {
            doc /* ir: tr_wait_after_fill_done
             * priority: 4
             */
        }
        transition tr_transfer_t1_t2_shut first transfer_t1_t2 accept shut_cmd do action : clear_history then shutdown {
            doc /* ir: tr_transfer_t1_t2_shut
             * priority: 1
             */
        }
        transition tr_transfer_t1_t2_stop first transfer_t1_t2 accept stop_cmd do action : save_history then paused {
            doc /* ir: tr_transfer_t1_t2_stop
             * priority: 2
             */
        }
        transition tr_transfer_t1_t2_low first transfer_t1_t2 if plc_101_level1 <= tk_101_low_level do action : start_timer { in timer = wait_after_transfer_timer; } then wait_after_transfer {
            doc /* ir: tr_transfer_t1_t2_low
             * priority: 4
             */
        }
        transition tr_wait_after_transfer_shut first wait_after_transfer accept shut_cmd do action : clear_history then shutdown {
            doc /* ir: tr_wait_after_transfer_shut
             * priority: 1
             */
        }
        transition tr_wait_after_transfer_stop first wait_after_transfer accept stop_cmd do action : save_history then paused {
            doc /* ir: tr_wait_after_transfer_stop
             * priority: 2
             */
        }
        transition tr_wait_after_transfer_done first wait_after_transfer if timer_expired(wait_after_transfer_timer) then drain_t2 {
            doc /* ir: tr_wait_after_transfer_done
             * priority: 4
             */
        }
        transition tr_drain_t2_shut first drain_t2 accept shut_cmd do action : clear_history then shutdown {
            doc /* ir: tr_drain_t2_shut
             * priority: 1
             */
        }
        transition tr_drain_t2_stop first drain_t2 accept stop_cmd do action : save_history then paused {
            doc /* ir: tr_drain_t2_stop
             * priority: 2
             */
        }
        transition tr_drain_t2_low first drain_t2 if plc_101_level2 <= tk_102_low_level do action : start_timer { in timer = wait_after_drain_timer; } then wait_after_drain {
            doc /* ir: tr_drain_t2_low
             * priority: 4
             */
        }
        transition tr_wait_after_drain_shut first wait_after_drain accept shut_cmd do action : clear_history then shutdown {
            doc /* ir: tr_wait_after_drain_shut
             * priority: 1
             */
        }
        transition tr_wait_after_drain_stop first wait_after_drain accept stop_cmd do action : save_history then paused {
            doc /* ir: tr_wait_after_drain_stop
             * priority: 2
             */
        }
        transition tr_wait_after_drain_done first wait_after_drain if timer_expired(wait_after_drain_timer) then fill_t1 {
            doc /* ir: tr_wait_after_drain_done
             * priority: 4
             */
        }
        transition tr_paused_shut first paused accept shut_cmd do action : clear_history then shutdown {
            doc /* ir: tr_paused_shut
             * priority: 1
             */
        }
        transition tr_paused_start first paused accept start_cmd then history {
            doc /* ir: tr_paused_start
             * priority: 3
             */
        }
        transition tr_shutdown_done first shutdown if plc_101_level1 <= tk_101_low_level and plc_101_level2 <= tk_102_low_level then idle {
            doc /* ir: tr_shutdown_done
             * priority: 4
             */
        }
    }

    requirement urs_ctl_001 {
        doc /* ir: urs_ctl_001
         * tags: URS-CTL-001
         * category: control
         * text: A STOP command received during a wait state shall freeze the wait timer rather than restart it.
         * source: engineering_data_register @ sheet Requirements_Register row 30, column C
         */
    }

    requirement urs_ctl_002 {
        doc /* ir: urs_ctl_002
         * tags: URS-CTL-002
         * category: control
         * text: START commands received while already running shall be ignored.
         * source: engineering_data_register @ sheet Requirements_Register row 31, column C
         */
    }

    requirement urs_ctl_003 {
        doc /* ir: urs_ctl_003
         * tags: URS-CTL-003
         * category: control
         * text: STOP commands received during SHUT mode shall be ignored until shutdown is complete.
         * source: engineering_data_register @ sheet Requirements_Register row 32, column C
         */
    }

    requirement urs_ctl_004 {
        doc /* ir: urs_ctl_004
         * tags: URS-CTL-004
         * category: control
         * text: START commands received during SHUT mode shall be ignored until shutdown is complete.
         * source: engineering_data_register @ sheet Requirements_Register row 33, column C
         */
    }

    requirement urs_ctl_005 {
        doc /* ir: urs_ctl_005
         * tags: URS-CTL-005
         * category: control
         * text: Shutdown completion shall require Tank 1 and Tank 2 to both be at or below their low-level setpoints.
         * source: engineering_data_register @ sheet Requirements_Register row 34, column C
         */
    }

    requirement urs_dat_001 {
        doc /* ir: urs_dat_001
         * tags: URS-DAT-001
         * category: data
         * text: Level values shall be represented internally in metres with a nominal valid range of 0.0 to 1.0 m.
         * source: engineering_data_register @ sheet Requirements_Register row 37, column C
         */
    }

    requirement urs_dat_002 {
        doc /* ir: urs_dat_002
         * tags: URS-DAT-002
         * category: data
         * text: Valve commands shall be represented as Boolean open/closed commands.
         * source: engineering_data_register @ sheet Requirements_Register row 38, column C
         */
    }

    requirement urs_fun_001 {
        doc /* ir: urs_fun_001
         * tags: URS-FUN-001, URS-F-001
         * category: functional
         * text: The controller shall start the automatic fill-transfer-drain sequence upon a valid START command when the process is idle or paused.
         * source: engineering_data_register @ sheet Requirements_Register row 4, column C (+1 more)
         */
    }

    requirement urs_fun_002 {
        doc /* ir: urs_fun_002
         * tags: URS-FUN-002, URS-F-002
         * category: functional
         * text: The automatic sequence shall open inlet valve V1 to fill Tank 1.
         * source: engineering_data_register @ sheet Requirements_Register row 5, column C (+1 more)
         */
    }

    requirement urs_fun_003 {
        doc /* ir: urs_fun_003
         * tags: URS-FUN-003, URS-F-003
         * category: functional
         * text: When Tank 1 reaches its high-level limit, V1 shall close.
         * source: engineering_data_register @ sheet Requirements_Register row 6, column C (+1 more)
         */
    }

    requirement urs_fun_004 {
        doc /* ir: urs_fun_004
         * tags: URS-FUN-004, URS-F-004
         * category: timing
         * text: After Tank 1 reaches the high-level limit, the controller shall wait 10 s before opening V2.
         * source: engineering_data_register @ sheet Requirements_Register row 7, column C (+1 more)
         */
    }

    requirement urs_fun_005 {
        doc /* ir: urs_fun_005
         * tags: URS-FUN-005, URS-F-005
         * category: functional
         * text: V2 shall transfer liquid from Tank 1 to Tank 2 until Tank 1 reaches its low-level limit.
         * source: engineering_data_register @ sheet Requirements_Register row 8, column C (+1 more)
         */
    }

    requirement urs_fun_007 {
        doc /* ir: urs_fun_007
         * tags: URS-FUN-007, URS-F-007
         * category: functional
         * text: V3 shall drain Tank 2 until Tank 2 reaches its low-level limit.
         * source: engineering_data_register @ sheet Requirements_Register row 10, column C (+1 more)
         */
    }

    requirement urs_int_001 {
        doc /* ir: urs_int_001
         * tags: URS-INT-001
         * category: interface
         * text: The controller shall receive two analog level measurements designated LT-101 and LT-102.
         * source: engineering_data_register @ sheet Requirements_Register row 27, column C
         */
    }

    requirement urs_int_002 {
        doc /* ir: urs_int_002
         * tags: URS-INT-002
         * category: interface
         * text: The controller shall receive momentary START, STOP and SHUT digital commands.
         * source: engineering_data_register @ sheet Requirements_Register row 28, column C
         */
    }

    requirement urs_int_003 {
        doc /* ir: urs_int_003
         * tags: URS-INT-003
         * category: interface
         * text: The controller shall provide three discrete valve-open commands to XV-101, XV-102 and XV-103.
         * source: engineering_data_register @ sheet Requirements_Register row 29, column C
         */
    }

    requirement urs_mod_001 {
        doc /* ir: urs_mod_001
         * tags: URS-MOD-001, URS-M-001
         * category: mode
         * text: STOP shall close V1, V2 and V3 and place the controller in a paused condition.
         * source: engineering_data_register @ sheet Requirements_Register row 12, column C (+1 more)
         */
    }

    requirement urs_mod_002 {
        doc /* ir: urs_mod_002
         * tags: URS-MOD-002, URS-M-002
         * category: mode
         * text: A START command following STOP shall continue the sequence from the point at which STOP was accepted.
         * source: engineering_data_register @ sheet Requirements_Register row 13, column C (+1 more)
         */
    }

    requirement urs_mod_003 {
        doc /* ir: urs_mod_003
         * tags: URS-MOD-003, URS-M-003
         * category: mode
         * text: SHUT shall command V2 and V3 open to drain both tanks and shall inhibit V1.
         * source: engineering_data_register @ sheet Requirements_Register row 14, column C (+1 more)
         */
    }

    requirement urs_mod_004 {
        doc /* ir: urs_mod_004
         * tags: URS-MOD-004, URS-M-004
         * category: mode
         * text: After shutdown draining is complete, all three valves shall be closed and the controller shall be in the initial idle configuration.
         * source: engineering_data_register @ sheet Requirements_Register row 15, column C (+1 more)
         */
    }

    requirement urs_per_002 {
        doc /* ir: urs_per_002
         * tags: URS-PER-002
         * category: performance
         * text: Tank 1 high-level setpoint shall be 0.80 m.
         * source: engineering_data_register @ sheet Requirements_Register row 22, column C
         */
    }

    requirement urs_per_003 {
        doc /* ir: urs_per_003
         * tags: URS-PER-003
         * category: performance
         * text: Tank 1 low-level setpoint shall be 0.05 m.
         * source: engineering_data_register @ sheet Requirements_Register row 23, column C
         */
    }

    requirement urs_per_004 {
        doc /* ir: urs_per_004
         * tags: URS-PER-004
         * category: performance
         * text: Tank 2 low-level setpoint shall be 0.05 m.
         * source: engineering_data_register @ sheet Requirements_Register row 24, column C
         */
    }

    requirement urs_per_005 {
        doc /* ir: urs_per_005
         * tags: URS-PER-005
         * category: timing
         * text: The post-transfer waiting time shall be 12 s.
         * source: engineering_data_register @ sheet Requirements_Register row 25, column C
         */
    }

    requirement urs_per_006 {
        doc /* ir: urs_per_006
         * tags: URS-PER-006
         * category: timing
         * text: The inter-cycle waiting time after Tank 2 reaches low level shall be 8 s.
         * source: engineering_data_register @ sheet Requirements_Register row 26, column C
         */
    }

    requirement urs_saf_001 {
        doc /* ir: urs_saf_001
         * tags: URS-SAF-001
         * category: safety
         * text: On loss of controller power, all process valves shall move to or remain in the closed position.
         * source: engineering_data_register @ sheet Requirements_Register row 16, column C
         */
    }

    requirement urs_saf_002 {
        doc /* ir: urs_saf_002
         * tags: URS-SAF-002
         * category: safety
         * text: SHUT shall have higher command priority than STOP; STOP shall have higher priority than START.
         * source: engineering_data_register @ sheet Requirements_Register row 17, column C
         */
    }

    requirement urs_saf_003 {
        doc /* ir: urs_saf_003
         * tags: URS-SAF-003
         * category: safety
         * text: V1 shall never be commanded open while V2 is open.
         * source: engineering_data_register @ sheet Requirements_Register row 18, column C
         */
    }

    requirement urs_saf_004 {
        doc /* ir: urs_saf_004
         * tags: URS-SAF-004
         * category: safety
         * text: During normal automatic operation, V2 and V3 shall not be open simultaneously.
         * source: engineering_data_register @ sheet Requirements_Register row 19, column C
         */
    }

    requirement urs_saf_005 {
        doc /* ir: urs_saf_005
         * tags: URS-SAF-005
         * category: safety
         * text: During SHUT mode, V2 and V3 may be open simultaneously.
         * source: engineering_data_register @ sheet Requirements_Register row 20, column C
         */
    }

    requirement urs_tst_001 {
        doc /* ir: urs_tst_001
         * tags: URS-TST-001
         * category: verification
         * text: The demonstration run shall simulate from 0 s through 900 s.
         * source: engineering_data_register @ sheet Requirements_Register row 35, column C
         * satisfied by, not modelled in SysML: system_stop_time (verification_only parameter; reported, not modelled)
         */
    }

    requirement urs_tst_002 {
        doc /* ir: urs_tst_002
         * tags: URS-TST-002
         * category: verification
         * text: The demonstration run shall apply START at 20 s, STOP at 220 s, START at 280 s, STOP at 650 s and SHUT at 700 s.
         * source: engineering_data_register @ sheet Requirements_Register row 36, column C
         * satisfied by, not modelled in SysML: pb_start_press_times (verification_only parameter; reported, not modelled), pb_stop_press_times (verification_only parameter; reported, not modelled), pb_shut_press_times (verification_only parameter; reported, not modelled)
         */
    }

    part system {
        doc /* the system: one usage per IR part, its connections, effective values and the requirements it satisfies */
        part drn_101 : FluidSink {
            doc /* ir: drn_101
             * name: Drain
             * tags: DRN-101, ambient1
             * source: engineering_data_register @ sheet Equipment_Schedule row 16, column D (+1 more)
             */
        }
        part lt_101 : LevelSensor {
            doc /* ir: lt_101
             * name: Tank 1 level transmitter
             * tags: LT-101, level1
             * source: urs_001 @ p.2 §5 (+1 more)
             * ASSUMPTION as_ideal_level_sensor: Level transmitters report the tank level exactly, with no 4-20 mA scaling, noise, delay or bad-quality handling.
             */
        }
        part lt_102 : LevelSensor {
            doc /* ir: lt_102
             * name: Tank 2 level transmitter
             * tags: LT-102, level2
             * source: urs_001 @ p.2 §5 (+1 more)
             * ASSUMPTION as_ideal_level_sensor: Level transmitters report the tank level exactly, with no 4-20 mA scaling, noise, delay or bad-quality handling.
             */
        }
        part pb_shut : CommandButton {
            doc /* ir: pb_shut
             * name: SHUT pushbutton
             * tags: PB-SHUT, shut, SHUT
             * source: urs_001 @ p.2 §5 (+2 more)
             * ASSUMPTION as_momentary_pulse: No pulse width is given for the pushbuttons; each press is assumed to be true for one 1 s logging interval, as in the reference trace. Only its rising edge matters.
             */
        }
        part pb_start : CommandButton {
            doc /* ir: pb_start
             * name: START pushbutton
             * tags: PB-START, start, START
             * source: urs_001 @ p.2 §5 (+1 more)
             * ASSUMPTION as_momentary_pulse: No pulse width is given for the pushbuttons; each press is assumed to be true for one 1 s logging interval, as in the reference trace. Only its rising edge matters.
             */
        }
        part pb_stop : CommandButton {
            doc /* ir: pb_stop
             * name: STOP pushbutton
             * tags: PB-STOP, stop, STOP
             * source: urs_001 @ p.2 §5 (+1 more)
             * ASSUMPTION as_momentary_pulse: No pulse width is given for the pushbuttons; each press is assumed to be true for one 1 s logging interval, as in the reference trace. Only its rising edge matters.
             */
        }
        part plc_101 : SequenceController {
            doc /* ir: plc_101
             * name: Sequence controller
             * tags: PLC-101, tankController
             * source: urs_001 @ p.1 §2 (+1 more)
             * ASSUMPTION as_event_driven_controller: The controller reacts to events and thresholds immediately rather than on its 100 ms scan; the scan time is recorded but not simulated.
             */
            port plc_101_level1 : ~RealSignal {
                doc /* ir: plc_101_level1
                 * role: level1
                 */
            }
            port plc_101_level2 : ~RealSignal {
                doc /* ir: plc_101_level2
                 * role: level2
                 */
            }
            port plc_101_shut : ~BoolSignal {
                doc /* ir: plc_101_shut
                 * role: shut
                 */
            }
            port plc_101_start : ~BoolSignal {
                doc /* ir: plc_101_start
                 * role: start
                 */
            }
            port plc_101_stop : ~BoolSignal {
                doc /* ir: plc_101_stop
                 * role: stop
                 */
            }
            port plc_101_valve1 : BoolSignal {
                doc /* ir: plc_101_valve1
                 * role: valve1
                 */
            }
            port plc_101_valve2 : BoolSignal {
                doc /* ir: plc_101_valve2
                 * role: valve2
                 */
            }
            port plc_101_valve3 : BoolSignal {
                doc /* ir: plc_101_valve3
                 * role: valve3
                 */
            }
            attribute :>> scan_time = 0.1 [s] {
                doc /* ir: plc_101_scan_time
                 * authority: cds_02
                 * original: 0.1 s
                 * source: engineering_data_register @ sheet Operating_Parameters row 18, column H (+1 more)
                 * ASSUMPTION as_event_driven_controller: The controller reacts to events and thresholds immediately rather than on its 100 ms scan; the scan time is recorded but not simulated.
                 */
            }
            attribute :>> wait_after_drain = 8.0 [s] {
                doc /* ir: plc_101_wait_after_drain
                 * authority: cr_004
                 * original: 8 s
                 * source: engineering_data_register @ sheet Requirements_Register row 26, column C (+2 more)
                 */
            }
            attribute :>> wait_after_fill = 10.0 [s] {
                doc /* ir: plc_101_wait_after_fill
                 * authority: urs_001
                 * original: 10 s
                 * source: urs_001 @ p.2 §4 (+2 more)
                 */
            }
            attribute :>> wait_after_transfer = 12.0 [s] {
                doc /* ir: plc_101_wait_after_transfer
                 * authority: cr_004
                 * original: 12 s
                 * source: engineering_data_register @ sheet Requirements_Register row 25, column C (+2 more)
                 */
            }
            exhibit state plc_101_sequence_behaviour : plc_101_sequence {
                doc /* behaviour: state machine plc_101_sequence */
                in :>> plc_101_level1 = plc_101.plc_101_level1.value;
                in :>> plc_101_level2 = plc_101.plc_101_level2.value;
                in :>> tk_101_high_level = tk_101.high_level;
                in :>> tk_101_low_level = tk_101.low_level;
                in :>> tk_102_low_level = tk_102.low_level;
                out :>> plc_101_valve1 = plc_101.plc_101_valve1.value;
                out :>> plc_101_valve2 = plc_101.plc_101_valve2.value;
                out :>> plc_101_valve3 = plc_101.plc_101_valve3.value;
                attribute :>> wait_after_fill_timer = plc_101.wait_after_fill;
                attribute :>> wait_after_transfer_timer = plc_101.wait_after_transfer;
                attribute :>> wait_after_drain_timer = plc_101.wait_after_drain;
            }
        }
        part src_101 : FluidSource {
            doc /* ir: src_101
             * name: Supply source
             * tags: SRC-101, source
             * source: engineering_data_register @ sheet Equipment_Schedule row 15, column D (+1 more)
             */
        }
        part tk_101 : Tank {
            doc /* ir: tk_101
             * name: Tank 1
             * tags: TK-101, tank1, T1
             * attribute: orientation = vertical
             * attribute: service = Intermediate receiving tank
             * source: urs_001 @ p.1 §2 (+1 more)
             */
            attribute :>> area = 1.2 [m^2] {
                doc /* ir: tk_101_area
                 * authority: mds_01
                 * original: 1.2 m^2
                 * source: engineering_data_register @ sheet Equipment_Schedule row 4, column E (+1 more)
                 */
            }
            attribute :>> height = 1.0 [m] {
                doc /* ir: tk_101_height
                 * authority: mds_01
                 * original: 1 m
                 * source: engineering_data_register @ sheet Equipment_Schedule row 4, column F
                 */
            }
            attribute :>> high_level = 0.8 [m] {
                doc /* ir: tk_101_high_level
                 * authority: cr_004
                 * original: 0.80 m
                 * source: engineering_data_register @ sheet Requirements_Register row 22, column C (+4 more)
                 */
            }
            attribute :>> initial_level = 0.05 [m] {
                doc /* ir: tk_101_initial_level
                 * authority: mds_01
                 * original: 0.05 m
                 * source: urs_001 @ p.2 §4 (+1 more)
                 */
            }
            attribute :>> low_level = 0.05 [m] {
                doc /* ir: tk_101_low_level
                 * authority: urs_001
                 * original: 0.05 m
                 * source: urs_001 @ p.2 §4 (+1 more)
                 */
            }
            attribute :>> max_working_level = 0.9 [m] {
                doc /* ir: tk_101_max_working_level
                 * authority: mds_01
                 * original: 0.9 m
                 * source: engineering_data_register @ sheet Equipment_Schedule row 4, column G
                 */
            }
        }
        part tk_102 : Tank {
            doc /* ir: tk_102
             * name: Tank 2
             * tags: TK-102, tank2, T2
             * attribute: orientation = vertical
             * attribute: service = Final receiving/drain tank
             * source: urs_001 @ p.1 §2 (+1 more)
             */
            attribute :>> area = 1.4 [m^2] {
                doc /* ir: tk_102_area
                 * authority: mds_01
                 * original: 1.4 m^2
                 * source: engineering_data_register @ sheet Equipment_Schedule row 5, column E (+1 more)
                 */
            }
            attribute :>> height = 1.0 [m] {
                doc /* ir: tk_102_height
                 * authority: mds_01
                 * original: 1 m
                 * source: engineering_data_register @ sheet Equipment_Schedule row 5, column F
                 */
            }
            attribute :>> initial_level = 0.05 [m] {
                doc /* ir: tk_102_initial_level
                 * authority: mds_01
                 * original: 0.05 m
                 * source: urs_001 @ p.2 §4 (+1 more)
                 */
            }
            attribute :>> low_level = 0.05 [m] {
                doc /* ir: tk_102_low_level
                 * authority: urs_001
                 * original: 0.05 m
                 * source: urs_001 @ p.2 §4 (+1 more)
                 */
            }
            attribute :>> max_working_level = 0.9 [m] {
                doc /* ir: tk_102_max_working_level
                 * authority: mds_01
                 * original: 0.9 m
                 * source: engineering_data_register @ sheet Equipment_Schedule row 5, column G
                 */
            }
        }
        part xv_101 : OnOffValve {
            doc /* ir: xv_101
             * name: Inlet valve to Tank 1
             * tags: XV-101, valve1, V1
             * attribute: fail_position = closed
             * source: urs_001 @ p.1 §2 (+1 more)
             * ASSUMPTION as_constant_flow: Each valve passes its constant nominal flow when commanded open and none when closed, independent of tank level; valve stroke time is neglected.
             */
            attribute :>> nominal_flow = 0.006 [m^3/s] {
                doc /* ir: xv_101_nominal_flow
                 * authority: mds_01
                 * original: 0.006 m^3/s
                 * source: engineering_data_register @ sheet Operating_Parameters row 15, column C (+2 more)
                 * ASSUMPTION as_constant_flow: Each valve passes its constant nominal flow when commanded open and none when closed, independent of tank level; valve stroke time is neglected.
                 */
            }
            attribute :>> open_stroke_time = 0.8 [s] {
                doc /* ir: xv_101_open_stroke_time
                 * authority: vd_vxs24
                 * original: 0.8 s
                 * source: vd_vxs24 @ p.1 §1
                 */
            }
        }
        part xv_102 : OnOffValve {
            doc /* ir: xv_102
             * name: Transfer valve Tank 1 to Tank 2
             * tags: XV-102, valve2, V2
             * attribute: fail_position = closed
             * source: urs_001 @ p.1 §2 (+1 more)
             * ASSUMPTION as_constant_flow: Each valve passes its constant nominal flow when commanded open and none when closed, independent of tank level; valve stroke time is neglected.
             */
            attribute :>> nominal_flow = 0.0045 [m^3/s] {
                doc /* ir: xv_102_nominal_flow
                 * authority: mds_01
                 * original: 0.0045 m^3/s
                 * source: engineering_data_register @ sheet Operating_Parameters row 16, column C (+2 more)
                 * ASSUMPTION as_constant_flow: Each valve passes its constant nominal flow when commanded open and none when closed, independent of tank level; valve stroke time is neglected.
                 */
            }
            attribute :>> open_stroke_time = 0.8 [s] {
                doc /* ir: xv_102_open_stroke_time
                 * authority: vd_vxs24
                 * original: 0.8 s
                 * source: vd_vxs24 @ p.1 §1
                 */
            }
        }
        part xv_103 : OnOffValve {
            doc /* ir: xv_103
             * name: Tank 2 drain valve
             * tags: XV-103, valve3, V3
             * attribute: fail_position = closed
             * source: urs_001 @ p.1 §2 (+1 more)
             * ASSUMPTION as_constant_flow: Each valve passes its constant nominal flow when commanded open and none when closed, independent of tank level; valve stroke time is neglected.
             */
            attribute :>> nominal_flow = 0.005 [m^3/s] {
                doc /* ir: xv_103_nominal_flow
                 * authority: mds_01
                 * original: 0.005 m^3/s
                 * source: engineering_data_register @ sheet Operating_Parameters row 17, column C (+2 more)
                 * ASSUMPTION as_constant_flow: Each valve passes its constant nominal flow when commanded open and none when closed, independent of tank level; valve stroke time is neglected.
                 */
            }
            attribute :>> open_stroke_time = 0.8 [s] {
                doc /* ir: xv_103_open_stroke_time
                 * authority: vd_vxs24
                 * original: 0.8 s
                 * source: vd_vxs24 @ p.1 §1
                 */
            }
        }
        connection if_ctl_01 connect lt_101.level_out to plc_101.plc_101_level1 {
            doc /* ir: if_ctl_01
             * from: lt_101_level_out -> to: plc_101_level1
             * carries: level measurement
             * source: engineering_data_register @ sheet Interface_Matrix row 10, column I
             */
        }
        connection if_ctl_02 connect lt_102.level_out to plc_101.plc_101_level2 {
            doc /* ir: if_ctl_02
             * from: lt_102_level_out -> to: plc_101_level2
             * carries: level measurement
             * source: engineering_data_register @ sheet Interface_Matrix row 11, column I
             */
        }
        connection if_ctl_03 connect pb_start.cmd_out to plc_101.plc_101_start {
            doc /* ir: if_ctl_03
             * from: pb_start_cmd_out -> to: plc_101_start
             * carries: command
             * source: engineering_data_register @ sheet Interface_Matrix row 12, column I
             */
        }
        connection if_ctl_04 connect pb_stop.cmd_out to plc_101.plc_101_stop {
            doc /* ir: if_ctl_04
             * from: pb_stop_cmd_out -> to: plc_101_stop
             * carries: command
             * source: engineering_data_register @ sheet Interface_Matrix row 13, column I
             */
        }
        connection if_ctl_05 connect pb_shut.cmd_out to plc_101.plc_101_shut {
            doc /* ir: if_ctl_05
             * from: pb_shut_cmd_out -> to: plc_101_shut
             * carries: command
             * source: engineering_data_register @ sheet Interface_Matrix row 14, column I
             */
        }
        connection if_ctl_06 connect plc_101.plc_101_valve1 to xv_101.cmd_in {
            doc /* ir: if_ctl_06
             * from: plc_101_valve1 -> to: xv_101_cmd_in
             * carries: open command
             * source: engineering_data_register @ sheet Interface_Matrix row 15, column F (+1 more)
             */
        }
        connection if_ctl_07 connect plc_101.plc_101_valve2 to xv_102.cmd_in {
            doc /* ir: if_ctl_07
             * from: plc_101_valve2 -> to: xv_102_cmd_in
             * carries: open command
             * source: engineering_data_register @ sheet Interface_Matrix row 16, column F (+1 more)
             */
        }
        connection if_ctl_08 connect plc_101.plc_101_valve3 to xv_103.cmd_in {
            doc /* ir: if_ctl_08
             * from: plc_101_valve3 -> to: xv_103_cmd_in
             * carries: open command
             * source: engineering_data_register @ sheet Interface_Matrix row 17, column F (+1 more)
             */
        }
        connection if_hyd_01 connect src_101.outlet to xv_101.inlet {
            doc /* ir: if_hyd_01
             * from: src_101_outlet -> to: xv_101_inlet
             * carries: liquid
             * source: engineering_data_register @ sheet Interface_Matrix row 4, column G (+1 more)
             */
        }
        connection if_hyd_02 connect xv_101.outlet to tk_101.inlet {
            doc /* ir: if_hyd_02
             * from: xv_101_outlet -> to: tk_101_inlet
             * carries: liquid
             * source: engineering_data_register @ sheet Interface_Matrix row 5, column G (+1 more)
             */
        }
        connection if_hyd_03 connect tk_101.outlet to xv_102.inlet {
            doc /* ir: if_hyd_03
             * from: tk_101_outlet -> to: xv_102_inlet
             * carries: liquid
             * source: engineering_data_register @ sheet Interface_Matrix row 6, column G (+1 more)
             */
        }
        connection if_hyd_04 connect xv_102.outlet to tk_102.inlet {
            doc /* ir: if_hyd_04
             * from: xv_102_outlet -> to: tk_102_inlet
             * carries: liquid
             * source: engineering_data_register @ sheet Interface_Matrix row 7, column G (+1 more)
             */
        }
        connection if_hyd_05 connect tk_102.outlet to xv_103.inlet {
            doc /* ir: if_hyd_05
             * from: tk_102_outlet -> to: xv_103_inlet
             * carries: liquid
             * source: engineering_data_register @ sheet Interface_Matrix row 8, column G (+1 more)
             */
        }
        connection if_hyd_06 connect xv_103.outlet to drn_101.inlet {
            doc /* ir: if_hyd_06
             * from: xv_103_outlet -> to: drn_101_inlet
             * carries: liquid
             * source: engineering_data_register @ sheet Interface_Matrix row 9, column G (+1 more)
             */
        }
        connection tk_101_lt_101 connect tk_101.level_out to lt_101.level_in {
            doc /* ir: tk_101_lt_101
             * from: tk_101_level_out -> to: lt_101_level_in
             * carries: level
             * source: engineering_data_register @ sheet Equipment_Schedule row 9, column D (+1 more)
             */
        }
        connection tk_102_lt_102 connect tk_102.level_out to lt_102.level_in {
            doc /* ir: tk_102_lt_102
             * from: tk_102_level_out -> to: lt_102_level_in
             * carries: level
             * source: engineering_data_register @ sheet Equipment_Schedule row 10, column D (+1 more)
             */
        }
        satisfy urs_ctl_001 by plc_101.plc_101_sequence_behaviour.tr_wait_after_fill_stop;
        satisfy urs_ctl_001 by plc_101.plc_101_sequence_behaviour.tr_wait_after_transfer_stop;
        satisfy urs_ctl_001 by plc_101.plc_101_sequence_behaviour.tr_wait_after_drain_stop;
        satisfy urs_ctl_001 by plc_101.plc_101_sequence_behaviour.tr_paused_start;
        satisfy urs_ctl_002 by plc_101.plc_101_sequence_behaviour;
        satisfy urs_ctl_003 by plc_101.plc_101_sequence_behaviour.shutdown;
        satisfy urs_ctl_004 by plc_101.plc_101_sequence_behaviour.shutdown;
        satisfy urs_ctl_005 by plc_101.plc_101_sequence_behaviour.tr_shutdown_done;
        satisfy urs_dat_001 by lt_101;
        satisfy urs_dat_001 by lt_102;
        satisfy urs_dat_002 by plc_101.plc_101_valve1;
        satisfy urs_dat_002 by plc_101.plc_101_valve2;
        satisfy urs_dat_002 by plc_101.plc_101_valve3;
        satisfy urs_fun_001 by plc_101.plc_101_sequence_behaviour.tr_idle_start;
        satisfy urs_fun_001 by plc_101.plc_101_sequence_behaviour.tr_paused_start;
        satisfy urs_fun_002 by plc_101.plc_101_sequence_behaviour.fill_t1;
        satisfy urs_fun_002 by xv_101;
        satisfy urs_fun_003 by plc_101.plc_101_sequence_behaviour.tr_fill_t1_high;
        satisfy urs_fun_003 by tk_101.high_level;
        satisfy urs_fun_004 by plc_101.plc_101_sequence_behaviour.wait_after_fill;
        satisfy urs_fun_004 by plc_101.wait_after_fill;
        satisfy urs_fun_005 by plc_101.plc_101_sequence_behaviour.transfer_t1_t2;
        satisfy urs_fun_005 by xv_102;
        satisfy urs_fun_005 by tk_101.low_level;
        satisfy urs_fun_007 by plc_101.plc_101_sequence_behaviour.drain_t2;
        satisfy urs_fun_007 by xv_103;
        satisfy urs_fun_007 by tk_102.low_level;
        satisfy urs_int_001 by lt_101;
        satisfy urs_int_001 by lt_102;
        satisfy urs_int_001 by if_ctl_01;
        satisfy urs_int_001 by if_ctl_02;
        satisfy urs_int_002 by pb_start;
        satisfy urs_int_002 by pb_stop;
        satisfy urs_int_002 by pb_shut;
        satisfy urs_int_002 by if_ctl_03;
        satisfy urs_int_002 by if_ctl_04;
        satisfy urs_int_002 by if_ctl_05;
        satisfy urs_int_003 by if_ctl_06;
        satisfy urs_int_003 by if_ctl_07;
        satisfy urs_int_003 by if_ctl_08;
        satisfy urs_mod_001 by plc_101.plc_101_sequence_behaviour.paused;
        satisfy urs_mod_001 by plc_101.plc_101_sequence_behaviour.tr_fill_t1_stop;
        satisfy urs_mod_001 by plc_101.plc_101_sequence_behaviour.tr_wait_after_fill_stop;
        satisfy urs_mod_001 by plc_101.plc_101_sequence_behaviour.tr_transfer_t1_t2_stop;
        satisfy urs_mod_001 by plc_101.plc_101_sequence_behaviour.tr_wait_after_transfer_stop;
        satisfy urs_mod_001 by plc_101.plc_101_sequence_behaviour.tr_drain_t2_stop;
        satisfy urs_mod_001 by plc_101.plc_101_sequence_behaviour.tr_wait_after_drain_stop;
        satisfy urs_mod_002 by plc_101.plc_101_sequence_behaviour.tr_paused_start;
        satisfy urs_mod_003 by plc_101.plc_101_sequence_behaviour.shutdown;
        satisfy urs_mod_004 by plc_101.plc_101_sequence_behaviour.tr_shutdown_done;
        satisfy urs_per_002 by tk_101.high_level;
        satisfy urs_per_003 by tk_101.low_level;
        satisfy urs_per_004 by tk_102.low_level;
        satisfy urs_per_005 by plc_101.wait_after_transfer;
        satisfy urs_per_006 by plc_101.wait_after_drain;
        satisfy urs_saf_001 by xv_101;
        satisfy urs_saf_001 by xv_102;
        satisfy urs_saf_001 by xv_103;
        satisfy urs_saf_002 by plc_101.plc_101_sequence_behaviour;
        satisfy urs_saf_003 by plc_101.plc_101_sequence_behaviour;
        satisfy urs_saf_004 by plc_101.plc_101_sequence_behaviour;
        satisfy urs_saf_005 by plc_101.plc_101_sequence_behaviour.shutdown;
    }
}
