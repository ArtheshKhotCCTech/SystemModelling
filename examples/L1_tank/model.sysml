// Generated by SpecAlive from the IR (specalive/generate/sysml.py). Regenerate, do not edit.
package system_model {
    doc /* model: system_model
     * description: Extracted from 12 source(s).
     * generated from the IR by SpecAlive (generate/sysml.py); regenerate, do not edit
     */
    private import ISQ::*;
    private import SI::*;
    private import ScalarValues::*;

    calc def timer_expired {
        doc /* IR expression language: true once the timer's state has been active for its duration */
        in timer : TimeValue;
        return : Boolean;
    }

    action def start_timer {
        doc /* IR action: start the timer from its full duration */
        in timer : TimeValue;
    }

    action def save_history {
        doc /* IR action: remember the active state and the remaining time of its timers */
    }

    action def clear_history {
        doc /* IR action: forget the remembered state */
    }

    port def BoolSignal {
        doc /* domain: signal_bool */
        out attribute value : Boolean;
    }

    port def FluidPort {
        doc /* domain: fluid */
        out attribute volume_flow : VolumeFlowRateValue;
    }

    port def RealSignal {
        doc /* domain: signal_real */
        out attribute value : Real;
    }

    part def CommandButton {
        doc /* kind: command_button
         * catalogue: Momentary operator pushbutton; true for a short pulse at each press time.
         */
        port cmd_out : BoolSignal;
    }

    part def FluidSink {
        doc /* kind: fluid_sink
         * catalogue: Ideal drain boundary; accepts whatever flow arrives.
         */
        port inlet : ~FluidPort;
    }

    part def FluidSource {
        doc /* kind: fluid_source
         * catalogue: Ideal supply boundary; delivers whatever flow downstream draws.
         */
        port outlet : FluidPort;
    }

    part def LevelSensor {
        doc /* kind: level_sensor
         * catalogue: Level transmitter passing the measured level to the controller unchanged.
         */
        port level_in : ~RealSignal;
        port level_out : RealSignal;
    }

    part def OnOffValve {
        doc /* kind: on_off_valve
         * catalogue: Two-position isolation valve treated as an ideal Boolean flow switch passing its nominal flow when commanded open.
         */
        attribute nominal_flow : VolumeFlowRateValue;
        port cmd_in : ~BoolSignal;
        port inlet : ~FluidPort;
        port outlet : FluidPort;
    }

    part def SequenceController {
        doc /* kind: sequence_controller
         * catalogue: Discrete sequence controller generated from the IR state machine it owns.
         * ports come from each IR part and are declared on its usage
         */
        attribute controller_scan_time : TimeValue;
        attribute wait_after_tank_1_high : TimeValue;
        attribute wait_after_tank_1_low : TimeValue;
        attribute wait_after_tank_2_low : TimeValue;
    }

    part def Tank {
        doc /* kind: tank
         * catalogue: Open vertical tank; level is the stored volume over a constant cross-section.
         */
        attribute area : AreaValue;
        attribute high_level_limit : LengthValue;
        attribute initial_level : LengthValue;
        attribute low_level_limit : LengthValue;
        port inlet : ~FluidPort;
        port level_out : RealSignal;
        port outlet : FluidPort;
    }

    attribute def shut_event {
        doc /* ir: shut_event
         * event of plc_101_sequence: rising edge of port plc_101_shut
         */
    }

    attribute def start_event {
        doc /* ir: start_event
         * event of plc_101_sequence: rising edge of port plc_101_start
         */
    }

    attribute def stop_event {
        doc /* ir: stop_event
         * event of plc_101_sequence: rising edge of port plc_101_stop
         */
    }

    state def plc_101_sequence {
        doc /* ir: plc_101_sequence
         * owner: plc_101
         * source: cds_02 @ table 2, row 10 (section '2. State Definitions') (+19 more)
         */
        in attribute plc_101_level1 : Real;
        in attribute plc_101_level2 : Real;
        in attribute tk_101_high_level_limit : LengthValue;
        in attribute tk_101_low_level_limit : LengthValue;
        in attribute tk_102_low_level_limit : LengthValue;
        out attribute plc_101_valve1 : Boolean;
        out attribute plc_101_valve2 : Boolean;
        out attribute plc_101_valve3 : Boolean;
        attribute wait_after_fill_timer : TimeValue {
            doc /* ir: wait_after_fill_timer
             * duration: parameter plc_101_wait_after_tank_1_high; counts only while its state is active
             */
        }
        attribute wait_after_transfer_timer : TimeValue {
            doc /* ir: wait_after_transfer_timer
             * duration: parameter plc_101_wait_after_tank_1_low; counts only while its state is active
             */
        }
        attribute wait_after_drain_timer : TimeValue {
            doc /* ir: wait_after_drain_timer
             * duration: parameter plc_101_wait_after_tank_2_low; counts only while its state is active
             */
        }
        entry; then idle;
        state idle {
            doc /* ir: idle
             * name: IDLE
             */
            entry action {
                assign plc_101_valve1 := false;
                assign plc_101_valve2 := false;
                assign plc_101_valve3 := false;
            }
        }
        state fill_t1 {
            doc /* ir: fill_t1
             * name: FILL_T1
             */
            entry action {
                assign plc_101_valve1 := true;
                assign plc_101_valve2 := false;
                assign plc_101_valve3 := false;
            }
        }
        state wait_after_fill {
            doc /* ir: wait_after_fill
             * name: WAIT_AFTER_FILL
             */
            entry action {
                assign plc_101_valve1 := false;
                assign plc_101_valve2 := false;
                assign plc_101_valve3 := false;
            }
        }
        state transfer_t1_t2 {
            doc /* ir: transfer_t1_t2
             * name: TRANSFER_T1_T2
             */
            entry action {
                assign plc_101_valve1 := false;
                assign plc_101_valve2 := true;
                assign plc_101_valve3 := false;
            }
        }
        state wait_after_transfer {
            doc /* ir: wait_after_transfer
             * name: WAIT_AFTER_TRANSFER
             */
            entry action {
                assign plc_101_valve1 := false;
                assign plc_101_valve2 := false;
                assign plc_101_valve3 := false;
            }
        }
        state drain_t2 {
            doc /* ir: drain_t2
             * name: DRAIN_T2
             */
            entry action {
                assign plc_101_valve1 := false;
                assign plc_101_valve2 := false;
                assign plc_101_valve3 := true;
            }
        }
        state wait_after_drain {
            doc /* ir: wait_after_drain
             * name: WAIT_AFTER_DRAIN
             */
            entry action {
                assign plc_101_valve1 := false;
                assign plc_101_valve2 := false;
                assign plc_101_valve3 := false;
            }
        }
        state paused {
            doc /* ir: paused
             * name: PAUSED
             */
            entry action {
                assign plc_101_valve1 := false;
                assign plc_101_valve2 := false;
                assign plc_101_valve3 := false;
            }
        }
        state shutdown {
            doc /* ir: shutdown
             * name: SHUTDOWN
             */
            entry action {
                assign plc_101_valve1 := false;
                assign plc_101_valve2 := true;
                assign plc_101_valve3 := true;
            }
        }
        state history {
            doc /* resume target: the state saved by the last save_history (UML shallow history); SysML v2 has no history pseudostate, so the IR's reserved target is a state here */
        }
        transition tr_idle_1 first idle accept start_event then fill_t1 {
            doc /* ir: tr_idle_1
             * priority: 1
             */
        }
        transition tr_idle_3 first idle accept shut_event then shutdown {
            doc /* ir: tr_idle_3
             * priority: 3
             */
        }
        transition tr_fill_t1_1 first fill_t1 if plc_101_level1 >= tk_101_high_level_limit do action : start_timer { in timer = wait_after_fill_timer; } then wait_after_fill {
            doc /* ir: tr_fill_t1_1
             * priority: 1
             */
        }
        transition tr_fill_t1_2 first fill_t1 accept stop_event do action : save_history then paused {
            doc /* ir: tr_fill_t1_2
             * priority: 2
             */
        }
        transition tr_fill_t1_3 first fill_t1 accept shut_event then shutdown {
            doc /* ir: tr_fill_t1_3
             * priority: 3
             */
        }
        transition tr_wait_after_fill_1 first wait_after_fill if timer_expired(wait_after_fill_timer) then transfer_t1_t2 {
            doc /* ir: tr_wait_after_fill_1
             * priority: 1
             */
        }
        transition tr_wait_after_fill_2 first wait_after_fill accept stop_event do action : save_history then paused {
            doc /* ir: tr_wait_after_fill_2
             * priority: 2
             */
        }
        transition tr_wait_after_fill_3 first wait_after_fill accept shut_event then shutdown {
            doc /* ir: tr_wait_after_fill_3
             * priority: 3
             */
        }
        transition tr_transfer_t1_t2_1 first transfer_t1_t2 if plc_101_level1 <= tk_101_low_level_limit do action : start_timer { in timer = wait_after_transfer_timer; } then wait_after_transfer {
            doc /* ir: tr_transfer_t1_t2_1
             * priority: 1
             */
        }
        transition tr_transfer_t1_t2_2 first transfer_t1_t2 accept stop_event do action : save_history then paused {
            doc /* ir: tr_transfer_t1_t2_2
             * priority: 2
             */
        }
        transition tr_transfer_t1_t2_3 first transfer_t1_t2 accept shut_event then shutdown {
            doc /* ir: tr_transfer_t1_t2_3
             * priority: 3
             */
        }
        transition tr_wait_after_transfer_1 first wait_after_transfer if timer_expired(wait_after_transfer_timer) then drain_t2 {
            doc /* ir: tr_wait_after_transfer_1
             * priority: 1
             */
        }
        transition tr_wait_after_transfer_2 first wait_after_transfer accept stop_event do action : save_history then paused {
            doc /* ir: tr_wait_after_transfer_2
             * priority: 2
             */
        }
        transition tr_wait_after_transfer_3 first wait_after_transfer accept shut_event then shutdown {
            doc /* ir: tr_wait_after_transfer_3
             * priority: 3
             */
        }
        transition tr_drain_t2_1 first drain_t2 if plc_101_level2 <= tk_102_low_level_limit do action : start_timer { in timer = wait_after_drain_timer; } then wait_after_drain {
            doc /* ir: tr_drain_t2_1
             * priority: 1
             */
        }
        transition tr_drain_t2_2 first drain_t2 accept stop_event do action : save_history then paused {
            doc /* ir: tr_drain_t2_2
             * priority: 2
             */
        }
        transition tr_drain_t2_3 first drain_t2 accept shut_event then shutdown {
            doc /* ir: tr_drain_t2_3
             * priority: 3
             */
        }
        transition tr_wait_after_drain_1 first wait_after_drain if timer_expired(wait_after_drain_timer) then fill_t1 {
            doc /* ir: tr_wait_after_drain_1
             * priority: 1
             */
        }
        transition tr_wait_after_drain_2 first wait_after_drain accept stop_event do action : save_history then paused {
            doc /* ir: tr_wait_after_drain_2
             * priority: 2
             */
        }
        transition tr_wait_after_drain_3 first wait_after_drain accept shut_event then shutdown {
            doc /* ir: tr_wait_after_drain_3
             * priority: 3
             */
        }
        transition tr_paused_1 first paused accept start_event do action : clear_history then history {
            doc /* ir: tr_paused_1
             * priority: 1
             */
        }
        transition tr_shutdown_1 first shutdown if plc_101_level1 <= tk_101_low_level_limit and plc_101_level2 <= tk_102_low_level_limit then idle {
            doc /* ir: tr_shutdown_1
             * priority: 1
             */
        }
    }

    requirement urs_ctl_001 {
        doc /* ir: urs_ctl_001
         * tags: URS-CTL-001
         * category: Control
         * text: A STOP command received during a wait state shall freeze the wait timer rather than restart it.
         * source: src_02_engineering_data_02_engineering_data_register_xlsx @ sheet Requirements_Register, row 30
         */
    }

    requirement urs_ctl_002 {
        doc /* ir: urs_ctl_002
         * tags: URS-CTL-002
         * category: Control
         * text: START commands received while already running shall be ignored.
         * source: src_02_engineering_data_02_engineering_data_register_xlsx @ sheet Requirements_Register, row 31
         */
    }

    requirement urs_ctl_003 {
        doc /* ir: urs_ctl_003
         * tags: URS-CTL-003
         * category: Control
         * text: STOP commands received during SHUT mode shall be ignored until shutdown is complete.
         * source: src_02_engineering_data_02_engineering_data_register_xlsx @ sheet Requirements_Register, row 32
         */
    }

    requirement urs_ctl_004 {
        doc /* ir: urs_ctl_004
         * tags: URS-CTL-004
         * category: Control
         * text: START commands received during SHUT mode shall be ignored until shutdown is complete.
         * source: src_02_engineering_data_02_engineering_data_register_xlsx @ sheet Requirements_Register, row 33
         */
    }

    requirement urs_ctl_005 {
        doc /* ir: urs_ctl_005
         * tags: URS-CTL-005
         * category: Control
         * text: Shutdown completion shall require Tank 1 and Tank 2 to both be at or below their low-level setpoints.
         * source: src_02_engineering_data_02_engineering_data_register_xlsx @ sheet Requirements_Register, row 34
         */
    }

    requirement urs_dat_001 {
        doc /* ir: urs_dat_001
         * tags: URS-DAT-001
         * category: Data
         * text: Level values shall be represented internally in metres with a nominal valid range of 0.0 to 1.0 m.
         * source: src_02_engineering_data_02_engineering_data_register_xlsx @ sheet Requirements_Register, row 37
         */
    }

    requirement urs_dat_002 {
        doc /* ir: urs_dat_002
         * tags: URS-DAT-002
         * category: Data
         * text: Valve commands shall be represented as Boolean open/closed commands.
         * source: src_02_engineering_data_02_engineering_data_register_xlsx @ sheet Requirements_Register, row 38
         */
    }

    requirement urs_f_001 {
        doc /* ir: urs_f_001
         * tags: URS-F-001
         * category: Functional
         * text: START shall initiate automatic operation when the system is in its initial condition.
         * source: urs_001 @ page 1, line 43
         */
    }

    requirement urs_f_002 {
        doc /* ir: urs_f_002
         * tags: URS-F-002
         * category: Functional
         * text: Normal operation shall fill Tank 1 by opening V1.
         * source: urs_001 @ page 1, line 44
         */
    }

    requirement urs_f_003 {
        doc /* ir: urs_f_003
         * tags: URS-F-003
         * category: Functional
         * text: V1 shall close when Tank 1 reaches the specified high-level limit.
         * source: urs_001 @ page 1, line 45
         */
    }

    requirement urs_f_004 {
        doc /* ir: urs_f_004
         * tags: URS-F-004
         * category: Functional
         * text: After a 10 s waiting period, V2 shall open and transfer liquid from Tank 1 to Tank 2.
         * source: urs_001 @ page 1, line 46
         */
    }

    requirement urs_f_005 {
        doc /* ir: urs_f_005
         * tags: URS-F-005
         * category: Functional
         * text: V2 shall close when Tank 1 reaches its minimum operating level.
         * source: urs_001 @ page 1, line 47
         */
    }

    requirement urs_f_006 {
        doc /* ir: urs_f_006
         * tags: URS-F-006
         * category: Functional
         * text: After a 10 s waiting period, V3 shall open and drain Tank 2.
         * source: urs_001 @ page 1, line 48
         */
    }

    requirement urs_f_007 {
        doc /* ir: urs_f_007
         * tags: URS-F-007
         * category: Functional
         * text: V3 shall close when Tank 2 reaches its minimum operating level.
         * source: urs_001 @ page 1, line 49
         */
    }

    requirement urs_f_008 {
        doc /* ir: urs_f_008
         * tags: URS-F-008
         * category: Functional
         * text: The automatic process shall continue cyclically unless stopped or shut down.
         * source: urs_001 @ page 1, line 50
         */
    }

    requirement urs_fun_001 {
        doc /* ir: urs_fun_001
         * tags: URS-FUN-001
         * category: Functional
         * text: The controller shall start the automatic fill-transfer-drain sequence upon a valid START command when the process is idle or paused.
         * source: src_02_engineering_data_02_engineering_data_register_xlsx @ sheet Requirements_Register, row 4
         */
    }

    requirement urs_fun_002 {
        doc /* ir: urs_fun_002
         * tags: URS-FUN-002
         * category: Functional
         * text: The automatic sequence shall open inlet valve V1 to fill Tank 1.
         * source: src_02_engineering_data_02_engineering_data_register_xlsx @ sheet Requirements_Register, row 5
         */
    }

    requirement urs_fun_003 {
        doc /* ir: urs_fun_003
         * tags: URS-FUN-003
         * category: Functional
         * text: When Tank 1 reaches its high-level limit, V1 shall close.
         * source: src_02_engineering_data_02_engineering_data_register_xlsx @ sheet Requirements_Register, row 6
         */
    }

    requirement urs_fun_004 {
        doc /* ir: urs_fun_004
         * tags: URS-FUN-004
         * category: Timing
         * text: After Tank 1 reaches the high-level limit, the controller shall wait 10 s before opening V2.
         * source: src_02_engineering_data_02_engineering_data_register_xlsx @ sheet Requirements_Register, row 7
         */
    }

    requirement urs_fun_005 {
        doc /* ir: urs_fun_005
         * tags: URS-FUN-005
         * category: Functional
         * text: V2 shall transfer liquid from Tank 1 to Tank 2 until Tank 1 reaches its low-level limit.
         * source: src_02_engineering_data_02_engineering_data_register_xlsx @ sheet Requirements_Register, row 8
         */
    }

    requirement urs_fun_007 {
        doc /* ir: urs_fun_007
         * tags: URS-FUN-007
         * category: Functional
         * text: V3 shall drain Tank 2 until Tank 2 reaches its low-level limit.
         * source: src_02_engineering_data_02_engineering_data_register_xlsx @ sheet Requirements_Register, row 10
         */
    }

    requirement urs_int_001 {
        doc /* ir: urs_int_001
         * tags: URS-INT-001
         * category: Interface
         * text: The controller shall receive two analog level measurements designated LT-101 and LT-102.
         * source: src_02_engineering_data_02_engineering_data_register_xlsx @ sheet Requirements_Register, row 27
         */
    }

    requirement urs_int_002 {
        doc /* ir: urs_int_002
         * tags: URS-INT-002
         * category: Interface
         * text: The controller shall receive momentary START, STOP and SHUT digital commands.
         * source: src_02_engineering_data_02_engineering_data_register_xlsx @ sheet Requirements_Register, row 28
         */
    }

    requirement urs_int_003 {
        doc /* ir: urs_int_003
         * tags: URS-INT-003
         * category: Interface
         * text: The controller shall provide three discrete valve-open commands to XV-101, XV-102 and XV-103.
         * source: src_02_engineering_data_02_engineering_data_register_xlsx @ sheet Requirements_Register, row 29
         */
    }

    requirement urs_m_001 {
        doc /* ir: urs_m_001
         * tags: URS-M-001
         * category: Functional
         * text: STOP shall close all three valves and suspend automatic operation until another operator command is received.
         * source: urs_001 @ page 1, lines 51-52
         */
    }

    requirement urs_m_002 {
        doc /* ir: urs_m_002
         * tags: URS-M-002
         * category: Functional
         * text: START after STOP shall continue the process operation rather than force a new empty-cycle initialization.
         * source: urs_001 @ page 1, lines 53-54
         */
    }

    requirement urs_m_003 {
        doc /* ir: urs_m_003
         * tags: URS-M-003
         * category: Functional
         * text: SHUT shall empty both tanks by opening V2 and V3 and shall inhibit V1.
         * source: urs_001 @ page 1, line 55
         */
    }

    requirement urs_m_004 {
        doc /* ir: urs_m_004
         * tags: URS-M-004
         * category: Functional
         * text: When shutdown emptying is achieved, V2 and V3 shall close and the controller shall return to the start configuration.
         * source: urs_001 @ page 1, lines 56-57
         */
    }

    requirement urs_mod_001 {
        doc /* ir: urs_mod_001
         * tags: URS-MOD-001
         * category: Mode
         * text: STOP shall close V1, V2 and V3 and place the controller in a paused condition.
         * source: src_02_engineering_data_02_engineering_data_register_xlsx @ sheet Requirements_Register, row 12
         */
    }

    requirement urs_mod_002 {
        doc /* ir: urs_mod_002
         * tags: URS-MOD-002
         * category: Mode
         * text: A START command following STOP shall continue the sequence from the point at which STOP was accepted.
         * source: src_02_engineering_data_02_engineering_data_register_xlsx @ sheet Requirements_Register, row 13
         */
    }

    requirement urs_mod_003 {
        doc /* ir: urs_mod_003
         * tags: URS-MOD-003
         * category: Mode
         * text: SHUT shall command V2 and V3 open to drain both tanks and shall inhibit V1.
         * source: src_02_engineering_data_02_engineering_data_register_xlsx @ sheet Requirements_Register, row 14
         */
    }

    requirement urs_mod_004 {
        doc /* ir: urs_mod_004
         * tags: URS-MOD-004
         * category: Mode
         * text: After shutdown draining is complete, all three valves shall be closed and the controller shall be in the initial idle configuration.
         * source: src_02_engineering_data_02_engineering_data_register_xlsx @ sheet Requirements_Register, row 15
         */
    }

    requirement urs_per_002 {
        doc /* ir: urs_per_002
         * tags: URS-PER-002
         * category: Performance
         * text: Tank 1 high-level setpoint shall be 0.80 m.
         * source: src_02_engineering_data_02_engineering_data_register_xlsx @ sheet Requirements_Register, row 22
         */
    }

    requirement urs_per_003 {
        doc /* ir: urs_per_003
         * tags: URS-PER-003
         * category: Performance
         * text: Tank 1 low-level setpoint shall be 0.05 m.
         * source: src_02_engineering_data_02_engineering_data_register_xlsx @ sheet Requirements_Register, row 23
         */
    }

    requirement urs_per_004 {
        doc /* ir: urs_per_004
         * tags: URS-PER-004
         * category: Performance
         * text: Tank 2 low-level setpoint shall be 0.05 m.
         * source: src_02_engineering_data_02_engineering_data_register_xlsx @ sheet Requirements_Register, row 24
         */
    }

    requirement urs_per_005 {
        doc /* ir: urs_per_005
         * tags: URS-PER-005
         * category: Timing
         * text: The post-transfer waiting time shall be 12 s.
         * source: src_02_engineering_data_02_engineering_data_register_xlsx @ sheet Requirements_Register, row 25
         */
    }

    requirement urs_per_006 {
        doc /* ir: urs_per_006
         * tags: URS-PER-006
         * category: Timing
         * text: The inter-cycle waiting time after Tank 2 reaches low level shall be 8 s.
         * source: src_02_engineering_data_02_engineering_data_register_xlsx @ sheet Requirements_Register, row 26
         */
    }

    requirement urs_saf_001 {
        doc /* ir: urs_saf_001
         * tags: URS-SAF-001
         * category: Safety
         * text: On loss of controller power, all process valves shall move to or remain in the closed position.
         * source: src_02_engineering_data_02_engineering_data_register_xlsx @ sheet Requirements_Register, row 16
         */
    }

    requirement urs_saf_002 {
        doc /* ir: urs_saf_002
         * tags: URS-SAF-002
         * category: Safety
         * text: SHUT shall have higher command priority than STOP; STOP shall have higher priority than START.
         * source: src_02_engineering_data_02_engineering_data_register_xlsx @ sheet Requirements_Register, row 17
         */
    }

    requirement urs_saf_003 {
        doc /* ir: urs_saf_003
         * tags: URS-SAF-003
         * category: Safety
         * text: V1 shall never be commanded open while V2 is open.
         * source: src_02_engineering_data_02_engineering_data_register_xlsx @ sheet Requirements_Register, row 18
         */
    }

    requirement urs_saf_004 {
        doc /* ir: urs_saf_004
         * tags: URS-SAF-004
         * category: Safety
         * text: During normal automatic operation, V2 and V3 shall not be open simultaneously.
         * source: src_02_engineering_data_02_engineering_data_register_xlsx @ sheet Requirements_Register, row 19
         */
    }

    requirement urs_saf_005 {
        doc /* ir: urs_saf_005
         * tags: URS-SAF-005
         * category: Safety
         * text: During SHUT mode, V2 and V3 may be open simultaneously.
         * source: src_02_engineering_data_02_engineering_data_register_xlsx @ sheet Requirements_Register, row 20
         */
    }

    requirement urs_tst_001 {
        doc /* ir: urs_tst_001
         * tags: URS-TST-001
         * category: Verification
         * text: The demonstration run shall simulate from 0 s through 900 s.
         * source: src_02_engineering_data_02_engineering_data_register_xlsx @ sheet Requirements_Register, row 35
         */
    }

    requirement urs_tst_002 {
        doc /* ir: urs_tst_002
         * tags: URS-TST-002
         * category: Verification
         * text: The demonstration run shall apply START at 20 s, STOP at 220 s, START at 280 s, STOP at 650 s and SHUT at 700 s.
         * source: src_02_engineering_data_02_engineering_data_register_xlsx @ sheet Requirements_Register, row 36
         */
    }

    part system {
        doc /* the system: one usage per IR part, its connections, effective values and the requirements it satisfies */
        part drn_101 : FluidSink {
            doc /* ir: drn_101
             * name: DRN-101
             * tags: DRN-101, ambient1
             * attribute: service = Drain from XV-103
             * source: cds_02 @ paragraph 19 (section '7. Naming Cross-Reference') (+3 more)
             * ASSUMPTION as_stated_02: DRN-101 is treated as an ideal sink.
             */
        }
        part lt_101 : LevelSensor {
            doc /* ir: lt_101
             * name: LT-101
             * tags: LT-101, level1
             * attribute: service = TK-101 level
             * source: cds_02 @ paragraph 19 (section '7. Naming Cross-Reference') (+3 more)
             */
        }
        part lt_102 : LevelSensor {
            doc /* ir: lt_102
             * name: LT-102
             * tags: LT-102, level2
             * attribute: service = TK-102 level
             * source: cds_02 @ paragraph 19 (section '7. Naming Cross-Reference') (+3 more)
             */
        }
        part pb_shut : CommandButton {
            doc /* ir: pb_shut
             * name: PB-SHUT
             * tags: PB-SHUT, shut
             * attribute: clarification = controlled process shutdown/drain, not an emergency-stop function
             * attribute: service = Controlled shutdown/drain
             * source: cds_02 @ paragraph 19 (section '7. Naming Cross-Reference') (+7 more)
             */
        }
        part pb_start : CommandButton {
            doc /* ir: pb_start
             * name: PB-START
             * tags: PB-START, start
             * attribute: service = Start/resume command
             * source: cds_02 @ paragraph 19 (section '7. Naming Cross-Reference') (+6 more)
             */
        }
        part pb_stop : CommandButton {
            doc /* ir: pb_stop
             * name: PB-STOP
             * tags: PB-STOP, stop
             * attribute: service = Pause command
             * source: cds_02 @ paragraph 19 (section '7. Naming Cross-Reference') (+6 more)
             */
        }
        part plc_101 : SequenceController {
            doc /* ir: plc_101
             * name: PLC-101
             * tags: PLC-101, tankController
             * attribute: service = Sequence and mode control
             * source: cds_02 @ paragraph 19 (section '7. Naming Cross-Reference') (+15 more)
             */
            port plc_101_level1 : ~RealSignal {
                doc /* ir: plc_101_level1
                 * role: level1
                 * source: src_02_engineering_data_02_engineering_data_register_xlsx @ sheet IO_List, row 7
                 */
            }
            port plc_101_level2 : ~RealSignal {
                doc /* ir: plc_101_level2
                 * role: level2
                 * source: src_02_engineering_data_02_engineering_data_register_xlsx @ sheet IO_List, row 8
                 */
            }
            port plc_101_shut : ~BoolSignal {
                doc /* ir: plc_101_shut
                 * role: shut
                 * source: src_02_engineering_data_02_engineering_data_register_xlsx @ sheet IO_List, row 6
                 */
            }
            port plc_101_start : ~BoolSignal {
                doc /* ir: plc_101_start
                 * role: start
                 * source: src_02_engineering_data_02_engineering_data_register_xlsx @ sheet IO_List, row 4
                 */
            }
            port plc_101_stop : ~BoolSignal {
                doc /* ir: plc_101_stop
                 * role: stop
                 * source: src_02_engineering_data_02_engineering_data_register_xlsx @ sheet IO_List, row 5
                 */
            }
            port plc_101_valve1 : BoolSignal {
                doc /* ir: plc_101_valve1
                 * role: valve1
                 * source: src_02_engineering_data_02_engineering_data_register_xlsx @ sheet IO_List, row 9
                 */
            }
            port plc_101_valve2 : BoolSignal {
                doc /* ir: plc_101_valve2
                 * role: valve2
                 * source: src_02_engineering_data_02_engineering_data_register_xlsx @ sheet IO_List, row 10
                 */
            }
            port plc_101_valve3 : BoolSignal {
                doc /* ir: plc_101_valve3
                 * role: valve3
                 * source: src_02_engineering_data_02_engineering_data_register_xlsx @ sheet IO_List, row 11
                 */
            }
            attribute :>> controller_scan_time = 0.1 [s] {
                doc /* ir: plc_101_controller_scan_time
                 * authority: cds_02
                 * original: 0.1 s
                 * source: src_02_engineering_data_02_engineering_data_register_xlsx @ sheet Operating_Parameters, row 18
                 */
            }
            attribute :>> wait_after_tank_1_high = 10.0 [s] {
                doc /* ir: plc_101_wait_after_tank_1_high
                 * authority: urs_001
                 * original: 10 s
                 * source: urs_001 @ page 2, lines 3-41 (+2 more)
                 */
            }
            attribute :>> wait_after_tank_1_low = 12.0 [s] {
                doc /* ir: plc_101_wait_after_tank_1_low
                 * authority: cr_004
                 * original: 12 s
                 * source: src_02_engineering_data_02_engineering_data_register_xlsx @ sheet Operating_Parameters, row 12 (+2 more)
                 */
            }
            attribute :>> wait_after_tank_2_low = 8.0 [s] {
                doc /* ir: plc_101_wait_after_tank_2_low
                 * authority: cr_004
                 * original: 8 s
                 * source: src_02_engineering_data_02_engineering_data_register_xlsx @ sheet Operating_Parameters, row 14 (+2 more)
                 */
            }
            exhibit state plc_101_sequence_behaviour : plc_101_sequence {
                doc /* behaviour: state machine plc_101_sequence */
                in :>> plc_101_level1 = plc_101.plc_101_level1.value;
                in :>> plc_101_level2 = plc_101.plc_101_level2.value;
                in :>> tk_101_high_level_limit = tk_101.high_level_limit;
                in :>> tk_101_low_level_limit = tk_101.low_level_limit;
                in :>> tk_102_low_level_limit = tk_102.low_level_limit;
                out :>> plc_101_valve1 = plc_101.plc_101_valve1.value;
                out :>> plc_101_valve2 = plc_101.plc_101_valve2.value;
                out :>> plc_101_valve3 = plc_101.plc_101_valve3.value;
                attribute :>> wait_after_fill_timer = plc_101.wait_after_tank_1_high;
                attribute :>> wait_after_transfer_timer = plc_101.wait_after_tank_1_low;
                attribute :>> wait_after_drain_timer = plc_101.wait_after_tank_2_low;
            }
        }
        part src_101 : FluidSource {
            doc /* ir: src_101
             * name: SRC-101
             * tags: SRC-101, source
             * attribute: service = Supply to XV-101
             * source: cds_02 @ paragraph 19 (section '7. Naming Cross-Reference') (+3 more)
             * ASSUMPTION as_stated_01: SRC-101 is treated as an ideal source.
             */
        }
        part tk_101 : Tank {
            doc /* ir: tk_101
             * name: TK-101
             * tags: TK-101, tank1, T1
             * attribute: orientation = Vertical tank
             * attribute: service = Intermediate receiving tank
             * source: cds_02 @ paragraph 19 (section '7. Naming Cross-Reference') (+7 more)
             */
            attribute :>> area = 1.2 [m^2] {
                doc /* ir: tk_101_area
                 * authority: src_02_engineering_data_02_engineering_data_register_xlsx
                 * original: 1.2 m^2
                 * source: src_02_engineering_data_02_engineering_data_register_xlsx @ sheet Equipment_Schedule, row 4 (+1 more)
                 */
            }
            attribute :>> high_level_limit = 0.8 [m] {
                doc /* ir: tk_101_high_level_limit
                 * authority: cr_004
                 * original: 0.8 m
                 * source: src_02_engineering_data_02_engineering_data_register_xlsx @ sheet Operating_Parameters, row 7 (+2 more)
                 */
            }
            attribute :>> initial_level = 0.05 [m] {
                doc /* ir: tk_101_initial_level
                 * authority: mds_01
                 * original: 0.05 m
                 * source: src_02_engineering_data_02_engineering_data_register_xlsx @ sheet Operating_Parameters, row 4 (+3 more)
                 */
            }
            attribute :>> low_level_limit = 0.05 [m] {
                doc /* ir: tk_101_low_level_limit
                 * authority: urs_001
                 * original: 0.05 m
                 * source: urs_001 @ page 2, lines 3-41 (+2 more)
                 */
            }
        }
        part tk_102 : Tank {
            doc /* ir: tk_102
             * name: TK-102
             * tags: TK-102, tank2, T2
             * attribute: orientation = Vertical tank
             * attribute: service = Final receiving/drain tank
             * source: cds_02 @ paragraph 19 (section '7. Naming Cross-Reference') (+8 more)
             */
            attribute :>> area = 1.4 [m^2] {
                doc /* ir: tk_102_area
                 * authority: src_02_engineering_data_02_engineering_data_register_xlsx
                 * original: 1.4 m^2
                 * source: src_02_engineering_data_02_engineering_data_register_xlsx @ sheet Equipment_Schedule, row 5 (+1 more)
                 */
            }
            attribute :>> initial_level = 0.05 [m] {
                doc /* ir: tk_102_initial_level
                 * authority: mds_01
                 * original: 0.05 m
                 * source: src_02_engineering_data_02_engineering_data_register_xlsx @ sheet Operating_Parameters, row 5 (+3 more)
                 */
            }
            attribute :>> low_level_limit = 0.05 [m] {
                doc /* ir: tk_102_low_level_limit
                 * authority: urs_001
                 * original: 0.05 m
                 * source: urs_001 @ page 2, lines 3-41 (+2 more)
                 */
            }
        }
        part xv_101 : OnOffValve {
            doc /* ir: xv_101
             * name: XV-101
             * tags: XV-101, valve1, V1
             * attribute: de_energized_position = Closed
             * attribute: fail_position = Closed
             * attribute: project_service = Feed to Tank 1
             * attribute: service = Feed source to TK-101
             * source: cds_02 @ paragraph 19 (section '7. Naming Cross-Reference') (+10 more)
             * ASSUMPTION as_stated_03: Constant-flow demo assumption.
             * ASSUMPTION as_stated_04: The dynamic valve stroke is neglected and each valve is treated as an ideal Boolean flow switch.
             */
            attribute :>> nominal_flow = 0.006 [m^3/s] {
                doc /* ir: xv_101_nominal_flow
                 * authority: mds_01
                 * original: 0.006 m^3/s
                 * source: src_02_engineering_data_02_engineering_data_register_xlsx @ sheet Operating_Parameters, row 15 (+3 more)
                 */
            }
        }
        part xv_102 : OnOffValve {
            doc /* ir: xv_102
             * name: XV-102
             * tags: XV-102, valve2, V2
             * attribute: de_energized_position = Closed
             * attribute: fail_position = Closed
             * attribute: project_service = Tank 1 transfer
             * attribute: service = TK-101 to TK-102
             * source: cds_02 @ paragraph 19 (section '7. Naming Cross-Reference') (+9 more)
             * ASSUMPTION as_stated_03: Constant-flow demo assumption.
             * ASSUMPTION as_stated_04: The dynamic valve stroke is neglected and each valve is treated as an ideal Boolean flow switch.
             */
            attribute :>> nominal_flow = 0.0045 [m^3/s] {
                doc /* ir: xv_102_nominal_flow
                 * authority: mds_01
                 * original: 0.0045 m^3/s
                 * source: src_02_engineering_data_02_engineering_data_register_xlsx @ sheet Operating_Parameters, row 16 (+2 more)
                 */
            }
        }
        part xv_103 : OnOffValve {
            doc /* ir: xv_103
             * name: XV-103
             * tags: XV-103, valve3, V3
             * attribute: de_energized_position = Closed
             * attribute: fail_position = Closed
             * attribute: project_service = Tank 2 drain
             * attribute: service = TK-102 to drain
             * source: cds_02 @ paragraph 19 (section '7. Naming Cross-Reference') (+9 more)
             * ASSUMPTION as_stated_03: Constant-flow demo assumption.
             * ASSUMPTION as_stated_04: The dynamic valve stroke is neglected and each valve is treated as an ideal Boolean flow switch.
             */
            attribute :>> nominal_flow = 0.005 [m^3/s] {
                doc /* ir: xv_103_nominal_flow
                 * authority: mds_01
                 * original: 0.005 m^3/s
                 * source: src_02_engineering_data_02_engineering_data_register_xlsx @ sheet Operating_Parameters, row 17 (+2 more)
                 */
            }
        }
        connection if_hyd_01 connect src_101.outlet to xv_101.inlet {
            doc /* ir: if_hyd_01
             * from: src_101_outlet -> to: xv_101_inlet
             * carries: Liquid
             * source: src_02_engineering_data_02_engineering_data_register_xlsx @ sheet Interface_Matrix, row 4 (+1 more)
             */
        }
        connection if_hyd_02 connect xv_101.outlet to tk_101.inlet {
            doc /* ir: if_hyd_02
             * from: xv_101_outlet -> to: tk_101_inlet
             * carries: Liquid
             * source: src_02_engineering_data_02_engineering_data_register_xlsx @ sheet Interface_Matrix, row 5 (+2 more)
             */
        }
        connection if_hyd_03 connect tk_101.outlet to xv_102.inlet {
            doc /* ir: if_hyd_03
             * from: tk_101_outlet -> to: xv_102_inlet
             * carries: Liquid
             * source: src_02_engineering_data_02_engineering_data_register_xlsx @ sheet Interface_Matrix, row 6 (+1 more)
             */
        }
        connection if_hyd_04 connect xv_102.outlet to tk_102.inlet {
            doc /* ir: if_hyd_04
             * from: xv_102_outlet -> to: tk_102_inlet
             * carries: Liquid
             * source: src_02_engineering_data_02_engineering_data_register_xlsx @ sheet Interface_Matrix, row 7 (+2 more)
             */
        }
        connection if_hyd_05 connect tk_102.outlet to xv_103.inlet {
            doc /* ir: if_hyd_05
             * from: tk_102_outlet -> to: xv_103_inlet
             * carries: Liquid
             * source: src_02_engineering_data_02_engineering_data_register_xlsx @ sheet Interface_Matrix, row 8 (+1 more)
             */
        }
        connection if_hyd_06 connect xv_103.outlet to drn_101.inlet {
            doc /* ir: if_hyd_06
             * from: xv_103_outlet -> to: drn_101_inlet
             * carries: Liquid
             * source: src_02_engineering_data_02_engineering_data_register_xlsx @ sheet Interface_Matrix, row 9 (+1 more)
             */
        }
        connection lt_101_level_out_to_plc_101_level1 connect lt_101.level_out to plc_101.plc_101_level1 {
            doc /* ir: lt_101_level_out_to_plc_101_level1
             * from: lt_101_level_out -> to: plc_101_level1
             * carries: signal_real
             * source: src_02_engineering_data_02_engineering_data_register_xlsx @ sheet IO_List, row 7 (+2 more)
             */
        }
        connection lt_102_level_out_to_plc_101_level2 connect lt_102.level_out to plc_101.plc_101_level2 {
            doc /* ir: lt_102_level_out_to_plc_101_level2
             * from: lt_102_level_out -> to: plc_101_level2
             * carries: signal_real
             * source: src_02_engineering_data_02_engineering_data_register_xlsx @ sheet IO_List, row 8 (+2 more)
             */
        }
        connection pb_shut_cmd_out_to_plc_101_shut connect pb_shut.cmd_out to plc_101.plc_101_shut {
            doc /* ir: pb_shut_cmd_out_to_plc_101_shut
             * from: pb_shut_cmd_out -> to: plc_101_shut
             * carries: signal_bool
             * source: src_02_engineering_data_02_engineering_data_register_xlsx @ sheet IO_List, row 6 (+1 more)
             */
        }
        connection pb_start_cmd_out_to_plc_101_start connect pb_start.cmd_out to plc_101.plc_101_start {
            doc /* ir: pb_start_cmd_out_to_plc_101_start
             * from: pb_start_cmd_out -> to: plc_101_start
             * carries: signal_bool
             * source: src_02_engineering_data_02_engineering_data_register_xlsx @ sheet IO_List, row 4 (+1 more)
             */
        }
        connection pb_stop_cmd_out_to_plc_101_stop connect pb_stop.cmd_out to plc_101.plc_101_stop {
            doc /* ir: pb_stop_cmd_out_to_plc_101_stop
             * from: pb_stop_cmd_out -> to: plc_101_stop
             * carries: signal_bool
             * source: src_02_engineering_data_02_engineering_data_register_xlsx @ sheet IO_List, row 5 (+1 more)
             */
        }
        connection plc_101_valve1_to_xv_101_cmd_in connect plc_101.plc_101_valve1 to xv_101.cmd_in {
            doc /* ir: plc_101_valve1_to_xv_101_cmd_in
             * from: plc_101_valve1 -> to: xv_101_cmd_in
             * carries: signal_bool
             * source: src_02_engineering_data_02_engineering_data_register_xlsx @ sheet IO_List, row 9 (+2 more)
             */
        }
        connection plc_101_valve2_to_xv_102_cmd_in connect plc_101.plc_101_valve2 to xv_102.cmd_in {
            doc /* ir: plc_101_valve2_to_xv_102_cmd_in
             * from: plc_101_valve2 -> to: xv_102_cmd_in
             * carries: signal_bool
             * source: src_02_engineering_data_02_engineering_data_register_xlsx @ sheet IO_List, row 10 (+2 more)
             */
        }
        connection plc_101_valve3_to_xv_103_cmd_in connect plc_101.plc_101_valve3 to xv_103.cmd_in {
            doc /* ir: plc_101_valve3_to_xv_103_cmd_in
             * from: plc_101_valve3 -> to: xv_103_cmd_in
             * carries: signal_bool
             * source: src_02_engineering_data_02_engineering_data_register_xlsx @ sheet IO_List, row 11 (+2 more)
             */
        }
        connection tk_101_level_out_to_lt_101_level_in connect tk_101.level_out to lt_101.level_in {
            doc /* ir: tk_101_level_out_to_lt_101_level_in
             * from: tk_101_level_out -> to: lt_101_level_in
             * carries: level
             * source: src_02_engineering_data_02_engineering_data_register_xlsx @ sheet Equipment_Schedule, row 4 (+1 more)
             */
        }
        connection tk_102_level_out_to_lt_102_level_in connect tk_102.level_out to lt_102.level_in {
            doc /* ir: tk_102_level_out_to_lt_102_level_in
             * from: tk_102_level_out -> to: lt_102_level_in
             * carries: level
             * source: src_02_engineering_data_02_engineering_data_register_xlsx @ sheet Equipment_Schedule, row 10 (+1 more)
             */
        }
    }
}
